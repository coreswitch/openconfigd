module free5gc-udr {
  namespace "http://free5gc.org/yang/free5gc-udr";

  prefix "free5gc-udr";

  import ietf-inet-types {
    prefix inet;
  }

  import free5gc-types {
    prefix free5gc;
  }

  grouping udr {
    leaf name {
      type string;
    }
    container sbi {
      uses free5gc:sbi;
    }
    container logger {
      container udr {
        uses free5gc:logger;
      }
      container path-util {
        uses free5gc:logger;
      }
      container openapi {
        uses free5gc:logger;
      }
      container mongodb-library {
        uses free5gc:logger;
      }
    }
  }
}
