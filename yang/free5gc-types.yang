module free5gc-types {
  namespace "http://free5gc.org/yang/free5gc-types";

  prefix "free5gc-types";

  import ietf-inet-types {
    prefix inet;
  }

  typedef mcc {
    type string {
      pattern '[0-9]{3}';
    }
    description "Mobile Country Code (3 digits string, digit: 0~9)";
  }

  typedef mnc {
    type string {
      pattern '[0-9]{2,3}';
    }
    description "Mobile Network Code (2 or 3 digits string, digit: 0~9)";
  }

  typedef sst {
    type uint8 {
      range "0 .. 255";
    }
    description "Slice/Service Type (uinteger, range: 0~255)";
  }

  typedef sd {
    type string {
      pattern '[0-9a-fA-F]{6}';
    }
    description "Slice Differentiator (3 bytes hex string, range: 000000~FFFFFF)";
  }

  typedef host-uri {
    type string {
      pattern '[a-z]+://([^/:?#]+)(:[0-9]{1,5})?';
    }
    description "Simplified host URI with scheme, host, port";
  }

  typedef debug-level {
    type enumeration {
      enum trace;
      enum debug;
      enum info;
      enum warn;
      enum error;
      enum fatal;
      enum panic;
    }
  }

  grouping plmnid {
    leaf mcc {
      type mcc;
    }
    leaf mnc {
      type mnc;
    }
  }

  grouping sbi {
    description "Service-based interface information";
    leaf scheme {
      type enumeration {
        enum http;
        enum https;
      }
    }
    leaf register-ipv4 {
      type inet:ipv4-address;
    }
    leaf binding-ipv4 {
      type inet:ipv4-address;
    }
    leaf port {
      type uint16;
    }
    container tls {
      leaf key {
        type string;
      }
      leaf pem {
        type string;
      }
    }
  }

  grouping logger {
    description "Logger behavior";
    leaf debug-level {
      type debug-level;
    }
    leaf report-caller {
      type boolean;
    }
  }
}
