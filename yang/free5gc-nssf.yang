module free5gc-nssf {
  namespace "http://free5gc.org/yang/free5gc-nssf";

  prefix "free5gc-nssf";

  import ietf-inet-types {
    prefix inet;
  }

  import free5gc-types {
    prefix free5gc;
  }

  grouping nssf {
    leaf name {
      type string;
    }
    container sbi {
      uses free5gc:sbi;
    }
    list service-name-list {
      key "service-name";
      leaf service-name {
        type enumeration {
          enum nnssf-nsselection;
          enum nnssf-nssaiavailability;
        }
      }
    }

    list supported-plmn-list {
      key "name";
      leaf name {
        type string;
      }
      leaf mcc {
        type free5gc:mcc;
      }
      leaf mnc {
        type free5gc:mnc;
      }
    }

    list supported-nssai-in-plmn-list {
      key "name";
      leaf name {
        type string;
      }
      leaf mcc {
        type free5gc:mcc;
      }
      leaf mnc {
        type free5gc:mnc;
      }
      list supported-snssai-list {
        key "name";
        leaf name {
          type string;
        }
        leaf sst {
          type free5gc:sst;
        }
        leaf sd {
          type free5gc:sd;
        }
      }
    }
    list nsi-list {
      key "name";
      leaf name {
        type string;
      }
      leaf sst {
        type free5gc:sst;
      }
      leaf sd {
        type free5gc:sd;
      }
      list nsi-information-list {
        key "name";
        leaf name {
          type string;
        }
        leaf nrfid {
          type string;
        }
        leaf nsiid {
          type string;
        }
      }
    }
    list amf-set-list {
      key "name";
      leaf name {
        type string;
      }
      leaf amf-setid {
        type uint32;
      }
      list amf-list {
        key "instance-id";
        leaf instance-id {
          type string;
        }
      }
      leaf nrf-amf-set {
        type string;
      }
      list supported-nssai-availability-data {
        key "tai";
        leaf tai {
          type string;
        }
        container plmnid {
          uses free5gc:plmnid;
        }
        leaf tac {
          type uint32;
        }
        list supported-snssai-list {
          key "name";
          leaf name {
            type string;
          }
          leaf sst {
            type free5gc:sst;
          }
          leaf sd {
            type free5gc:sd;
          }
        }
      }
    }
    list amf-list {
      key "name";
      leaf name {
        type string;
      }
      leaf nfid {
        type string;
      }
      list supported-nssai-availability-data {
        key "tai";
        leaf tai {
          type string;
        }
        container plmnid {
          uses free5gc:plmnid;
        }
        leaf tac {
          type uint32;
        }
        list supported-snssai-list {
          key "name";
          leaf name {
            type string;
          }
          leaf sst {
            type free5gc:sst;
          }
          leaf sd {
            type free5gc:sd;
          }
        }
      }
    }
    list ta-list {
      key "name";
      leaf name {
        type string;
      }
      container plmnid {
        uses free5gc:plmnid;
      }
      leaf tac {
        type uint32;
      }
      leaf access-type {
        type enumeration {
          enum 3GPP_ACCESS;
          enum NON_3GPP_ACCESS;
        }
      }
      list supported-snssai-list {
        key "name";
        leaf name {
          type string;
        }
        leaf sst {
          type free5gc:sst;
        }
        leaf sd {
          type free5gc:sd;
        }
      }
      list restricted-snssai-list {
        key "name";
        leaf name {
          type string;
        }
        container home-plmnid {
          uses free5gc:plmnid;
        }
        list snssai-list {
          key "name";
          leaf name {
            type string;
          }
          leaf sst {
            type free5gc:sst;
          }
          leaf sd {
            type free5gc:sd;
          }
        }
      }
    }
    list mapping-list-from-plmn {
      key "operator-name";
      leaf operator-name {
        type string;
      }
      container home-plmnid {
        uses free5gc:plmnid;
      }
      list mapping-of-snssai {
        key "name";
        leaf name {
          type string;
        }
        container serving-snssai {
          leaf sst {
            type free5gc:sst;
          }
          leaf sd {
            type free5gc:sd;
          }
        }
        container home-snssai {
          leaf sst {
            type free5gc:sst;
          }
          leaf sd {
            type free5gc:sd;
          }
        }
      }
    }
    container logger {
      container nssf {
        uses free5gc:logger;
      }
      container path-util {
        uses free5gc:logger;
      }
      container openapi {
        uses free5gc:logger;
      }
    }
  }
}
