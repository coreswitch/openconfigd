module free5gc-ausf {
  namespace "http://free5gc.org/yang/free5gc-ausf";

  prefix "free5gc-ausf";

  import ietf-inet-types {
    prefix inet;
  }

  import free5gc-types {
    prefix free5gc;
  }

  grouping ausf {
    leaf name {
      type string;
    }
    container sbi {
      uses free5gc:sbi;
    }
    list service-name-list {
      key "service-name";
      leaf service-name {
        type enumeration {
          enum nausf-auth;
        }
      }
    }
    list plmn-support-list {
      key "name";
      leaf name {
        type string;
      }
      container plmnid {
        uses free5gc:plmnid;
      }
    }
    leaf groupid {
      type string;
    }
    container logger {
      container ausf {
        uses free5gc:logger;
      }
      container path-util {
        uses free5gc:logger;
      }
      container openapi {
        uses free5gc:logger;
      }
    }
  }
}
