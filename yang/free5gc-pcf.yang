module free5gc-pcf {
  namespace "http://free5gc.org/yang/free5gc-pcf";

  prefix "free5gc-pcf";

  import ietf-inet-types {
    prefix inet;
  }

  import free5gc-types {
    prefix free5gc;
  }

  grouping pcf {
    leaf name {
      type string;
    }
    container sbi {
      uses free5gc:sbi;
    }
    list service-name-list {
      key "service-name";
      leaf service-name {
        type enumeration {
          enum npcf-eventexposure;
          enum npcf-am-policy-control;
          enum npcf-smpolicycontrol;
          enum npcf-bdtpolicycontrol;
          enum npcf-policyauthorization;
          enum npcf-eventexposure;
          enum npcf-ue-policy-control;
        }
      }
      leaf supp-feat {
        type string;
      }
    }
    leaf time-format {
      type string;
    }
    leaf default-bdt-refid {
      type string;
    }
    container logger {
      container pcf {
        uses free5gc:logger;
      }
      container path-util {
        uses free5gc:logger;
      }
      container openapi {
        uses free5gc:logger;
      }
    }
  }
}
