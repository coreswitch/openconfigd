module free5gc-sepp {
  namespace "http://free5gc.org/yang/free5gc-amf";

  prefix "free5gc-sepp";

  import ietf-inet-types {
    prefix inet;
  }

  import free5gc-types {
    prefix free5gc;
  }

  grouping sepp {
    container local {
      leaf url {
        type string;
      }
      container plmnid {
        uses free5gc:plmnid;
      }
    }
    list remote {
      key "name";
      leaf name {
        type string;
      }
      container plmnid {
        uses free5gc:plmnid;
      }
      leaf url {
        type string;
      }
    }
    container sbi {
      leaf nrf-url {
        type string;
      }
      container plmnid {
        uses free5gc:plmnid;
      }
    }
    leaf disable-client {
      type empty;
    }
    leaf disable-server {
      type empty;
    }
    leaf retry-interval {
      type uint32;
    }
    leaf retry-max-count {
      type uint32;
    }
    container logger {
      container sepp {
        uses free5gc:logger;
      }
    }
  }
}
