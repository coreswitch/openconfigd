module free5gc-udm {
  namespace "http://free5gc.org/yang/free5gc-udm";

  prefix "free5gc-udm";

  import ietf-inet-types {
    prefix inet;
  }

  import free5gc-types {
    prefix free5gc;
  }

  grouping udm {
    leaf name {
      type string;
    }
    container sbi {
      uses free5gc:sbi;
    }
    list service-name-list {
      key "service-name";
      leaf service-name {
        type enumeration {
          enum nudm-sdm;
          enum nudm-uecm;
          enum nudm-ueau;
          enum nudm-ee;
          enum nudm-pp;
        }
      }
    }
    container keys {
      leaf udm-profile-ahn-public-key {
        type string;
      }
      leaf udm-profile-ahn-private-key {
        type string;
      }
      leaf udm-profile-bhn-public-key {
        type string;
      }
      leaf udm-profile-bhn-private-key {
        type string;
      }
    }
    container logger {
      container udm {
        uses free5gc:logger;
      }
      container path-util {
        uses free5gc:logger;
      }
      container openapi {
        uses free5gc:logger;
      }
    }
  }
}
