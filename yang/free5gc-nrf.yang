module free5gc-nrf {
  namespace "http://free5gc.org/yang/free5gc-nrf";

  prefix "free5gc-nrf";

  import ietf-inet-types {
    prefix inet;
  }

  import free5gc-types {
    prefix free5gc;
  }

  grouping nrf {
    leaf name {
      type string;
    }
    container sbi {
      uses free5gc:sbi;
    }
    list service-name-list {
      key "service-name";
      leaf service-name {
        type enumeration {
          enum nnrf-nfm;
          enum nnrf-disc;
        }
      }
    }
    container default-plmnid {
      uses free5gc:plmnid;
    }
    container logger {
      container nrf {
        uses free5gc:logger;
      }
      container path-util {
        uses free5gc:logger;
      }
      container openapi {
        uses free5gc:logger;
      }
      container mongodb-library {
        uses free5gc:logger;
      }
    }
  }
}
