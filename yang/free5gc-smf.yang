module free5gc-smf {
  namespace "http://free5gc.org/yang/free5gc-smf";

  prefix "free5gc-smf";

  import ietf-inet-types {
    prefix inet;
  }

  import free5gc-types {
    prefix free5gc;
  }

  grouping smf {
    leaf name {
      type string;
    }
    container sbi {
      uses free5gc:sbi;
    }
    list service-name-list {
      key "service-name";
      leaf service-name {
        type enumeration {
          enum nsmf-pdusession;
          enum nsmf-event-exposure;
          enum nsmf-oam;
        }
      }
    }

    list snssai {
      key "name";
      leaf name {
        type string;
      }
      leaf sst {
        type free5gc:sst;
      }
      leaf sd {
        type free5gc:sd;
      }
      list dnn {
        key "name";
        leaf name {
          type string;
        }
        container dns {
          leaf ipv4 {
            type inet:ipv4-address;
          }
        }
      }
    }

    container pfcp {
      leaf addr {
            type inet:ipv4-address;
      }
    }
    
    container userplane-information {
      list up-nodes {
        key "name";
        leaf name {
          type string;
        }
        leaf type {
          type enumeration {
            enum AN;
            enum UPF;
          }
        }
        leaf node-id {
          type inet:ipv4-address;
        }
        leaf an-ip {
          type string;
        }
        leaf dnn {
          type string;
        }
        list snssai {
          key "name";
          leaf name {
            type string;
          }
          leaf sst {
            type free5gc:sst;
          }
          leaf sd {
            type free5gc:sd;
          }
          list dnn {
            key "name";
            leaf name {
              type string;
            }
            list pools {
              key "cidr";
              leaf cidr {
                type inet:ipv4-prefix;
              }
            }
            list dnai-list {
              key "name";
              leaf name {
                type string;
              }
            }
            list pdu-session-types {
              key "name";
              leaf name {
                type string;
              }
            }
          }
        }
        list interfaces {
          key "name";
          leaf name {
            type string;
          }
          leaf interface-type {
            type enumeration {
              enum N3;
              enum N9;
            }
          }
          list endpoints {
            key "addr";
            leaf addr {
              type inet:ipv4-address;
            }
          }
          leaf network-instance {
            type string;
          }
        }
      }
      list links {
        key "name";
        leaf name {
          type string;
        }
        leaf A {
          type string;
        }
        leaf B {
          type string;
        }
      }
    }
    leaf ulcl {
      type boolean;
    }
    container logger {
      container smf {
        uses free5gc:logger;
      }
      container nas {
        uses free5gc:logger;
      }
      container ngap {
        uses free5gc:logger;
      }
      container aper {
        uses free5gc:logger;
      }
      container path-util {
        uses free5gc:logger;
      }
      container openapi {
        uses free5gc:logger;
      }
    }
  }
}
