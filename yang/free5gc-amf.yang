module free5gc-amf {
  namespace "http://free5gc.org/yang/free5gc-amf";

  prefix "free5gc-amf";

  import ietf-inet-types {
    prefix inet;
  }

  import free5gc-types {
    prefix free5gc;
  }

  grouping amf {
    leaf name {
      type string;
    }
    list ngap-ip-list {
      key "address";
      leaf address {
        type inet:ipv4-address;
      }
    }
    container sbi {
      uses free5gc:sbi;
    }
    list service-name-list {
      key "service-name";
      leaf service-name {
        type enumeration {
          enum namf-comm;
          enum namf-evts;
          enum namf-mt;
          enum namf-loc;
          enum namf-oam;
        }
      }
    }
    list served-guami-list {
      key "name";
      leaf name {
        type string;
      }
      container plmnid {
        uses free5gc:plmnid;
      }
      leaf amfid {
        type string;
      }
    }
    list support-tai-list {
      key "name";
      leaf name {
        type string;
      }
      container plmnid {
        uses free5gc:plmnid;
      }
      leaf tac {
        // TS 38.413 9.3.3.10 OCTET STRING (SIZE(3))
        type string;
      }
    }
    list plmn-support-list {
      key "name";
      leaf name {
        type string;
      }
      container plmnid {
        uses free5gc:plmnid;
      }
      list snssai-list {
        key "name";
        leaf name {
          type string;
        }
        leaf sst {
          type free5gc:sst;
        }
        leaf sd {
          type free5gc:sd;
        }
      }
    }
    list support-dnn-list {
      key "name";
      leaf name {
        type string;
      }
    }
    container security {
      leaf-list integrity-order {
        type enumeration {
          enum NIA2;
          enum NIA0;
        }
      }
      leaf-list ciphering-order {
        type enumeration {
          enum NEA2;
          enum NEA0;
        }
      }
    }
    container network-name {
      leaf full {
        type string;
      }
      leaf short {
        type string;
      }
    }
    container network-feature-support-5gs {
      leaf enable {
        type boolean;
      }
      leaf length {
        type uint8 {
          range 1..3;
        }
      }
      leaf ims-vops {
        type uint8 {
            range 0..1;
        }
      }
      leaf emc {
        type uint8 {
            range 0..3;
        }
      }
      leaf emf {
        type uint8 {
            range 0..3;
        }
      }
      leaf iwk-n26 {
        type uint8 {
            range 0..1;
        }
      }
      leaf mpsi {
        type uint8 {
            range 0..1;
        }
      }
      leaf emc-n3 {
        type uint8 {
            range 0..1;
        }
      }
      leaf mcsi {
        type uint8 {
            range 0..1;
        }
      }
    }
    leaf t3502-value {
      type uint32;
    }
    leaf t3512-value {
      type uint32;
    }
    leaf non3gpp-deregistration-timer-value {
      type uint32;
    }
    container t3513 {
      leaf enable {
        type boolean;
      }
      leaf expire-time {
        type uint32;
      }
      leaf max-retry-times {
        type uint32;
      }
    }
    container t3522 {
      leaf enable {
        type boolean;
      }
      leaf expire-time {
        type uint32;
      }
      leaf max-retry-times {
        type uint32;
      }
    }
    container t3550 {
      leaf enable {
        type boolean;
      }
      leaf expire-time {
        type uint32;
      }
      leaf max-retry-times {
        type uint32;
      }
    }
    container t3560 {
      leaf enable {
        type boolean;
      }
      leaf expire-time {
        type uint32;
      }
      leaf max-retry-times {
        type uint32;
      }
    }
    container t3565 {
      leaf enable {
        type boolean;
      }
      leaf expire-time {
        type uint32;
      }
      leaf max-retry-times {
        type uint32;
      }
    }
    container t3570 {
      leaf enable {
        type boolean;
      }
      leaf expire-time {
        type uint32;
      }
      leaf max-retry-times {
        type uint32;
      }
    }
    container logger {
      container amf {
        uses free5gc:logger;
      }
      container nas {
        uses free5gc:logger;
      }
      container fsm {
        uses free5gc:logger;
      }
      container ngap {
        uses free5gc:logger;
      }
      container aper {
        uses free5gc:logger;
      }
    }
  }
}
