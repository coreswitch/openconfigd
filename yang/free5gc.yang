module free5gc {
  yang-version "1";

  namespace "https://free5gc.org/";
  prefix "free5gc";

  import ietf-inet-types {
    prefix inet;
  }

  import free5gc-amf {
    prefix amf;
  }

  import free5gc-smf {
    prefix smf;
  }

  import free5gc-nrf {
    prefix nrf;
  }

  import free5gc-pcf {
    prefix pcf;
  }

  import free5gc-udm {
    prefix udm;
  }

  import free5gc-udr {
    prefix udr;
  }

  import free5gc-ausf {
    prefix ausf;
  }

  import free5gc-nssf {
    prefix nssf;
  }

  import free5gc-sepp {
    prefix sepp;
  }

  container amf {
    uses "amf:amf";
  }

  container smf {
    uses "smf:smf";
  }

  container nrf {
    uses "nrf:nrf";
  }

  container pcf {
    uses "pcf:pcf";
  }

  container udm {
    uses "udm:udm";
  }

  container udr {
    uses "udr:udr";
  }

  container ausf {
    uses "ausf:ausf";
  }

  container nssf {
    uses "nssf:nssf";
  }

  container sepp {
    uses "sepp:sepp";
  }

  container mongodb {
    leaf name {
      type string;
    }
    leaf url {
      type string;
    }
  }
  leaf nrf-uri {
    type string;
  }

  container system {
    description
      "System group configuration.";

    leaf hostname {
      type inet:domain-name;
      description
        "The name of the host.  This name can be a single domain
        label or the fully qualified domain name of the host.";
    }
    container etcd {
      list endpoints {
        key "url";
        leaf url {
          type string;
        }
      }
      leaf path {
        type string;
      }
    }
  }
}
